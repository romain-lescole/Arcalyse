# Véhicule de démonstration — exigences
Exigences de démonstration d'Arcature : tous les types de données, titres de chapitre, relations.

# Specification: Exigences du véhicule
- ReqIF.Description: Exigences de niveau système du véhicule de démonstration.

## _ch_generalites: Généralités

### EX-001: Masse maximale
Le véhicule doit peser moins de 1 500 kg en ordre de marche.
Hors passagers & bagages.
- Statut: Validée
- Lots: Mécanique, Électrique
- Priorité: 1
- Masse max (kg): 1500.0
- Vérifiée: true
- Échéance: 2026-12-31T00:00:00+01:00
- Origine: Cahier des charges client, § 3.1

### EX-002: Autonomie
L'autonomie doit atteindre 400 km (cycle WLTP).
- Commentaire: À confirmer avec le fournisseur des batteries

### EX-011: Alerte du conducteur
Une alerte sonore et visuelle précède tout freinage automatique.
- Dépend de -> EX-010

## _ch_securite: Sécurité

### EX-010: Freinage d'urgence
Le freinage d'urgence doit :
- arrêter le véhicule depuis 100 km/h en moins de 40 m ;
- rester disponible en cas de perte de l'alimentation principale.
- Statut: Proposée
- Raffine -> EX-001

# Specification: Exigences logicielles

## _r_attente: Exigence en attente
