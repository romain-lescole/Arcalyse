# Drone d'inspection — exigences
Exigences d'essai d'Arcature : images et pièces jointes des textes XHTML (archive .reqifz).

# Specification: Exigences système

## _o_c1: Généralités (Titre)

### SYS-001: Mission (Exigence)
Le drone doit inspecter une ligne électrique de 10 km sans recharge.
- Statut: Validée
- Priorité: Haute
- Vérification: Essai
- Criticité: 3
- Date de revue: 2026-11-06T09:00:00+01:00

### SYS-002: Architecture (Exigence)
L'architecture du drone suit le schéma ci-dessous :
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- Statut: Validée
- Priorité: Haute
- Vérification: Revue
- Criticité: 2
- Date de revue: 2026-11-06T09:00:00+01:00

## _o_c2: Performances (Titre)

### SYS-010: Autonomie (Exigence)
L'autonomie en vol doit atteindre 45 min dans les conditions du tableau :
| Vent | Température |
| --- | --- |
| ≤ 30 km/h | -10 à 40 °C |
- Statut: Proposée
- Priorité: Haute
- Vérification: Essai
- Criticité: 3
- Date de revue: 2026-11-06T09:00:00+01:00
- raffine -> SYS-001

### SYS-011: Charge utile (Exigence)
La masse de la charge utile ne dépasse pas 1,2 kg (voir l'objet incorporé) :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
- Statut: Proposée
- Priorité: Moyenne
- Vérification: Analyse
- Criticité: 2
- Date de revue: 2026-11-06T09:00:00+01:00

### SYS-012: Portée radio (Exigence)
La liaison radio couvre 5 km en vue directe (courbe de mesure manquante :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).
- Statut: Rejetée
- Priorité: Basse
- Vérification: Essai
- Criticité: 1
- Date de revue: 2026-11-06T09:00:00+01:00

### SYS-013: Conformité (Exigence)
Le drone respecte la réglementation (annexe :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).
- Statut: Validée
- Priorité: Moyenne
- Vérification: Revue
- Date de revue: 2026-11-06T09:00:00+01:00

# Specification: Exigences logicielles

## _o_c3: Logiciel de vol (Titre)

### LOG-001: Pilotage automatique (Exigence)
Le logiciel de vol maintient la trajectoire à ± 2 m.
- Statut: Validée
- Priorité: Haute
- Vérification: Essai
- Criticité: 3
- Date de revue: 2026-11-06T09:00:00+01:00
- dérive de -> SYS-001

### LOG-002: Retour automatique (Exigence)
En perte de liaison, le logiciel ramène le drone au point de départ.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
- Statut: Proposée
- Priorité: Haute
- Vérification: Simulation
- Criticité: 3
- Date de revue: 2026-11-06T09:00:00+01:00
- dérive de -> SYS-001

### LOG-003: Journal de vol (Exigence)
Le logiciel enregistre la télémétrie à 10 Hz.
- Date de revue: 2026-11-06T09:00:00+01:00
- dérive de -> SYS-010
